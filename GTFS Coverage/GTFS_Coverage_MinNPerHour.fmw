FME workspace GTFS_Coverage_MinNPerHour.fmw

Parameters:
- MinServicePerHour = 6   # Minimum number of services per hour
- p_download_dir = C:\Users\sabzer\OneDrive - Blacktown City Council\Desktop\test   # Download Path
- p_zip_basename = TGFS_181125   # File Name
- outFolder = \\bccfiler\shared\Shared\DEPT\PD\SPED\7. Data and Analytics\03_GIS\BCC Internal\Bus Stations   # Choose output folder
- outName = stops   # File Name
- outFormat = shp   # GeoPackage (.gpkg),gpkg%Shape File (.shp),shp%Excel (.xlsx),xslx Choose Output Format

Note: Stage 1 - Data Preparation
Note: Download GTFS, build stop geometries for the LGA, and join stops → stop_times → trips → routes to create a clean input table for analysis
Note: Stage 2 - Data Analysis
Note: For each weekday and weekend day, calculate services per stop and hour, apply the user-defined minimum services per hour, and flag stops that meet the coverage rule within a specific time window
Note: Stage 3 - Combine Results & Prepare Outputs
Note: Combine weekday & weekend coverage results, join them to stop geometries, and keep only the required attributes before writing outputs
Note: Stage 3 - Outputs
Note: Write the final stop-coverage results to multiple formats (GPKG< SHP, XLSX)
Creator
    GEOMTYPE = Geometry Object
    NUM = 1
    CREATED -> FeatureReader_2 [INITIATOR]
    CREATED -> StringConcatenator

Bookmark: Download and Extract CSV files
Note: Create zip_path from user's input
StringConcatenator
    ACTION = Create New Attribute
    PARM_LINE = fme_basicstring:17%1%17%4:$(p_download_dir)\$(p_zip_basename).zip
    VAL_ATTR = _zip_path
    -> HTTPCaller
Note: Download GTFS data and locate / in the user's desired folder
HTTPCaller
    CLIENT_CERTIFICATE_TYPE = NONE
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = @Value(_zip_path)
    REDIRECT_AUTH = ORIGINAL_DOMAIN_ONLY
    RESPONSE_TYPE = File
    STATUS_CODE_ATTR = _http_status_code
    TARGET_URL = https://opendata.transport.nsw.gov.au/data/dataset/d1f68d4f-b778-44df-9823-cf2fa922e47f/resource/67974f14-01bf-47b7-bfa5-c7f2f8a950ca/download/full_greater_sydney_gtfs_static_0.zip
    TRANSFER_TIMEOUT_LENGTH = 90
    USE_COOKIES = No
    VERIFY_SSL_CERTIFICATES = Yes
    -> ZipExtractor
Note: Extract the zipped file to access all CSVs
ZipExtractor
    PRESERVE = No
    RECURSIVE = No
    REPLACE = No
    ZIP_PATH = @Value(_response_file_path)
    File -> Tester
    File -> Tester_2
    File -> Tester_3
    File -> Tester_4
    File -> Tester_5

Bookmark: Getting bus stations based on stops.txt in the LGA
Note: Filter stops.txt
Tester
    BOOL_OP = OR
    TEST_CLAUSE = CASE_INSENSITIVE_TEST @Value(path_windows) CONTAINS stops
    TEST_MODE = CASE_INSENSITIVE_TEST
    PASSED -> FeatureReader [INITIATOR]
Note: Read stops.txt
FeatureReader
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer
AttributeExposer
    ATTR_TABLE = stop_id,varchar(12),level_id,varchar(8),location_type,uint8,parent_station,varchar(9),platform_code,varchar(6),stop_code,uint32,stop_lat,real64,stop_lon,real64,stop_name,varchar(76),wheelchair_boarding,uint8
    -> VertexCreator
Note: Assign Geometry
VertexCreator
    MEASURE_TYPE_LOOKUP = CONTINUOUS
    MODE = REPLACE
    REMOVE_ATTRIBUTES = No
    XVAL = @Value(stop_lon)
    YVAL = @Value(stop_lat)
    MEASURE_TYPE = Continuous
    MODE_NAME = Replace with Point
    -> CoordinateSystemSetter
CoordinateSystemSetter
    COORDSYS = EPSG:4326
    -> Reprojector
Note: Reproject_To_LL-GDA2020_FME
Reprojector
    DEST = LL-GDA2020_FME
    INTERPOLATION_TYPE = NearestNeighbor
    RASTER_CELL_SIZE = PreserveCells
    RASTER_TOLERANCE = 0.0
    SOURCE = EPSG:4326
    REPROJECTED -> Reprojector_2
Note: Reproject to EPSG:7856
Reprojector_2
    DEST = EPSG:7856
    INTERPOLATION_TYPE = NearestNeighbor
    RASTER_CELL_SIZE = PreserveCells
    RASTER_TOLERANCE = 0.0
    REPROJECTED -> SpatialFilter [Candidate]
Note: Blacktown LGA
FeatureReader_2
    ATTRIBUTES = Blacktown_LGA,"LGA_CODE21,LGA_NAME21,STE_CODE21,STE_NAME21,AUS_CODE21,AUS_NAME21,AREASQKM21,LOCI_URI21,SHAPE_Leng,SHAPE_Area,fid"
    ATTR_ACCUM_MODE = Only Use Result
    CLIP_TO_ENVELOPE = NO
    COMBINE_GEOM = Use Result
    DATASET = \\bccfiler\shared\Shared\DEPT\PD\SPED\7. Data and Analytics\03_GIS\BCC Internal\Affordable Housing\Blacktown_LGA.gpkg
    FORMAT = OGCGEOPACKAGE
    GEOMETRY_TYPES = Blacktown_LGA,"""geom,fme_area"""
    INITIATOR_FIRST_OUTPUT = default
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = SELECTFEATTYPES
    Blacktown_LGA -> Reprojector_3
Note: Reprojector to 7856
Reprojector_3
    DEST = EPSG:7856
    INTERPOLATION_TYPE = NearestNeighbor
    RASTER_CELL_SIZE = PreserveCells
    RASTER_TOLERANCE = 0.0
    REPROJECTED -> SpatialFilter [Filter]
Note: All Stops in LGA
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureJoiner_2 [LEFT]

Bookmark: Join stops to stop_times
Note: Fiklter stop_times.txt
Tester_3
    BOOL_OP = OR
    TEST_CLAUSE = CASE_INSENSITIVE_TEST @Value(path_windows) CONTAINS stop_times.txt
    TEST_MODE = CASE_INSENSITIVE_TEST
    PASSED -> FeatureReader_4 [INITIATOR]
Note: Read stop_times
FeatureReader_4
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer_3
AttributeExposer_3
    ATTR_TABLE = arrival_time,uint32,departure_time,uint32,drop_off_type,uint8,pickup_type,uint8,shape_dist_traveled,real64,stop_headsign,varchar(30),stop_id,uint32,stop_note,varchar(5),stop_sequence,uint8,timepoint,uint8,trip_id,varchar(35)
    -> FeatureJoiner_2 [RIGHT]
FeatureJoiner_2
    ATTR_CONFLICT_RES_LOOKUP = USE_LEFT
    GEOMETRY_HANDLING_LOOKUP = USE_LEFT
    JOIN_KEYS = stop_id stop_id STRING
    JOIN_MODE = Inner
    ATTR_CONFLICT_RES = Prefer Left
    GEOMETRY_HANDLING = Prefer Left
    JOINED -> FeatureJoiner [LEFT]
    <REJECTED> -> Logger
Note: stop_id in the right table is null
Logger
    LOG_FEATURE = LOG_ONLY
    MAXCOORDS = 20
    MAXFEATS = 20
    MESSAGE = Feature is:
    SEVERITY = INFO

Bookmark: join stops_stop_times to trips
Note: Fiklter trips.txt
Tester_2
    BOOL_OP = OR
    TEST_CLAUSE = CASE_INSENSITIVE_TEST @Value(path_windows) CONTAINS trips.txt
    TEST_MODE = CASE_INSENSITIVE_TEST
    PASSED -> FeatureReader_3 [INITIATOR]
Note: Read trips.txt
FeatureReader_3
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer_2
AttributeExposer_2
    ATTR_TABLE = bikes_allowed,varchar(200),block_id,varchar(7),direction_id,uint8,route_direction,varchar(136),route_id,varchar(14),service_id,varchar(13),shape_id,varchar(19),trip_headsign,varchar(50),trip_id,varchar(35),trip_note,varchar(5),wheelchair_accessible,uint8
    -> FeatureJoiner [RIGHT]
FeatureJoiner
    ATTR_CONFLICT_RES_LOOKUP = USE_LEFT
    GEOMETRY_HANDLING_LOOKUP = USE_LEFT
    JOIN_KEYS = trip_id trip_id AUTO
    JOIN_MODE = Inner
    ATTR_CONFLICT_RES = Prefer Left
    GEOMETRY_HANDLING = Prefer Left
    JOINED -> FeatureJoiner_3 [LEFT]

Bookmark: Join stops_stop_times_trips to routes
Note: Fiklter routes.txt
Tester_4
    BOOL_OP = OR
    TEST_CLAUSE = CASE_INSENSITIVE_TEST @Value(path_windows) CONTAINS routes.txt
    TEST_MODE = CASE_INSENSITIVE_TEST
    PASSED -> FeatureReader_5 [INITIATOR]
Note: Read routes.txt
FeatureReader_5
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer_4
AttributeExposer_4
    ATTR_TABLE = agency_id,varchar(5),exact_times,uint8,route_color,varchar(6),route_desc,varchar(37),route_id,varchar(14),route_long_name,varchar(151),route_short_name,varchar(5),route_text_color,varchar(6),route_type,uint16
    -> FeatureJoiner_3 [RIGHT]
FeatureJoiner_3
    ATTR_CONFLICT_RES_LOOKUP = USE_LEFT
    GEOMETRY_HANDLING_LOOKUP = USE_LEFT
    JOIN_KEYS = route_id route_id AUTO
    JOIN_MODE = Inner
    ATTR_CONFLICT_RES = Prefer Left
    GEOMETRY_HANDLING = Prefer Left
    JOINED -> Tester_6
Note: Filter normal buses (route_type = 700)
Tester_6
    BOOL_OP = OR
    TEST_CLAUSE = TEST @Value(route_type) = 700
    TEST_MODE = TEST
    PASSED -> FeatureJoiner_4 [LEFT]

Bookmark: Join stops_stop_times_trips_routes to Calendar.txt
Note: Fiklter Calendar.txt
Tester_5
    BOOL_OP = OR
    TEST_CLAUSE = CASE_INSENSITIVE_TEST @Value(path_windows) CONTAINS calendar.txt
    TEST_MODE = CASE_INSENSITIVE_TEST
    PASSED -> FeatureReader_6 [INITIATOR]
Note: Read Calendar.txt
FeatureReader_6
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = @Value(path_windows)
    FORMAT = CSV2
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer_5
AttributeExposer_5
    ATTR_TABLE = service_id,varchar(13),start_date,uint32,end_date,uint32,monday,uint8,tuesday,uint8,wednesday,uint8,thursday,uint8,friday,uint8,saturday,uint8,sunday,uint8
    -> FeatureJoiner_4 [RIGHT]
FeatureJoiner_4
    ATTR_CONFLICT_RES_LOOKUP = USE_LEFT
    GEOMETRY_HANDLING_LOOKUP = USE_LEFT
    JOIN_KEYS = service_id service_id AUTO
    JOIN_MODE = Inner
    ATTR_CONFLICT_RES = Prefer Left
    GEOMETRY_HANDLING = Prefer Left
    JOINED -> AttributeKeeper

Bookmark: Prepare input for analysis
Note: Keep only stop_id and calendar attributes
AttributeKeeper
    CREATE_BULK_MODE_FEATURES = NO
    KEEP_ATTRS = stop_id,arrival_time,departure_time,service_id,route_type,start_date,end_date,monday,tuesday,wednesday,thursday,friday,saturday,sunday,stop_name,route_desc,route_direction
    -> AttributeManager
Note: Add hour field based on departure time
AttributeManager
    ATTR_TABLE:
      SET_TO hh_text (varchar(200)) = @Substring(@Value(departure_time),0,2)
      SET_TO hour (real64) = @Evaluate(@fmod(int(@Value(hh_text)), 24)
        )
    -> Tester_7
    -> Tester_9
    -> Tester_11
    -> Tester_13
    -> Tester_15
    -> Tester_17
    -> Tester_19
    -> FeatureJoiner_11 [RIGHT]

Bookmark: Monday
Note: Service on Mondays 6-21
Tester_7
    BOOL_OP = COMPOSITE
    COMPOSITE_TEST = 1 AND 2 AND 3
    TEST_CLAUSE:
      TEST @Value(monday) = 1
      TEST @Value(hour) >= 6
      TEST @Value(hour) < 21
    TEST_MODE = TEST
    PASSED -> StatisticsCalculator
Note: Total count of services per stop_id, hour
StatisticsCalculator
    ATTR_ACCUM_MODE = None
    CALCULATION_MODE = NUMERIC
    FEAT_STATS = hour,NUMERIC_MODE,,,COUNT,,,,,,,,,,
    GROUP_BY = stop_id hour
    SUMMARY -> AttributeManager_3
Note: Rename attribute
AttributeManager_3
    ATTR_TABLE = RENAME_SET_VALUE hour.total_count > service per hour (uint64)
    -> Tester_8
Note: If there are >=N services in every hour
Tester_8
    BOOL_OP = OR
    TEST_CLAUSE = TEST @Value(service per hour) >= $(MinServicePerHour)
    TEST_MODE = TEST
    PASSED -> StatisticsCalculator_8
Note: Count of hours with ≥N services per stop
StatisticsCalculator_8
    ATTR_ACCUM_MODE = None
    CALCULATION_MODE = NUMERIC
    FEAT_STATS = hour,NUMERIC_MODE,,,COUNT,,,,,,,,,,
    GROUP_BY = stop_id
    SUMMARY -> Tester_21
Note: Stops with >=N services in 6-21
Tester_21
    BOOL_OP = OR
    TEST_CLAUSE = TEST @Value(hour.total_count) = 15
    TEST_MODE = TEST
    PASSED -> FeatureJoiner_5 [LEFT]

Bookmark: Tuesday
Note: Service on Tuesdays 6-21
Tester_9
    BOOL_OP = COMPOSITE
    COMPOSITE_TEST = 1 AND 2 AND 3
    TEST_CLAUSE:
      TEST @Value(tuesday) = 1
      TEST @Value(hour) >= 6
      TEST @Value(hour) < 21
    TEST_MODE = TEST
    PASSED -> StatisticsCalculator_2
Note: Total count of services per stop_id, hour
StatisticsCalculator_2
    ATTR_ACCUM_MODE = None
    CALCULATION_MODE = NUMERIC
    FEAT_STATS = hour,NUMERIC_MODE,,,COUNT,,,,,,,,,,
    GROUP_BY = stop_id hour
    SUMMARY -> AttributeManager_4
Note: Rename attribute
AttributeManager_4
    ATTR_TABLE = RENAME_SET_VALUE hour.total_count > service per hour (uint64)
    -> Tester_10
Note: If there are >=N services in every hour
Tester_10
    BOOL_OP = OR
    TEST_CLAUSE = TEST @Value(service per hour) >= $(MinServicePerHour)
    TEST_MODE = TEST
    PASSED -> StatisticsCalculator_9
Note: Count of hours with ≥N services per stop
StatisticsCalculator_9
    ATTR_ACCUM_MODE = None
    CALCULATION_MODE = NUMERIC
    FEAT_STATS = hour,NUMERIC_MODE,,,COUNT,,,,,,,,,,
    GROUP_BY = stop_id
    SUMMARY -> Tester_22
Note: Stops with >=N services in 6-21
Tester_22
    BOOL_OP = OR
    TEST_CLAUSE = TEST @Value(hour.total_count) = 15
    TEST_MODE = TEST
    PASSED -> FeatureJoiner_5 [RIGHT]

Bookmark: Joins data together & join back to geometry/ attributes
FeatureJoiner_5
    ATTR_CONFLICT_RES_LOOKUP = USE_RIGHT
    GEOMETRY_HANDLING_LOOKUP = USE_RIGHT
    JOIN_KEYS = stop_id stop_id AUTO
    JOIN_MODE = Inner
    ATTR_CONFLICT_RES = Prefer Right
    GEOMETRY_HANDLING = Prefer Right
    JOINED -> FeatureJoiner_6 [LEFT]
FeatureJoiner_6
    ATTR_CONFLICT_RES_LOOKUP = USE_LEFT
    GEOMETRY_HANDLING_LOOKUP = USE_LEFT
    JOIN_KEYS = stop_id stop_id AUTO
    JOIN_MODE = Inner
    ATTR_CONFLICT_RES = Prefer Left
    GEOMETRY_HANDLING = Prefer Left
    JOINED -> FeatureJoiner_7 [LEFT]
FeatureJoiner_7
    ATTR_CONFLICT_RES_LOOKUP = USE_LEFT
    GEOMETRY_HANDLING_LOOKUP = USE_LEFT
    JOIN_KEYS = stop_id stop_id AUTO
    JOIN_MODE = Inner
    ATTR_CONFLICT_RES = Prefer Left
    GEOMETRY_HANDLING = Prefer Left
    JOINED -> FeatureJoiner_8 [LEFT]
Note: Weekdays Passed
FeatureJoiner_8
    ATTR_CONFLICT_RES_LOOKUP = USE_LEFT
    GEOMETRY_HANDLING_LOOKUP = USE_LEFT
    JOIN_KEYS = stop_id stop_id AUTO
    JOIN_MODE = Inner
    ATTR_CONFLICT_RES = Prefer Left
    GEOMETRY_HANDLING = Prefer Left
    JOINED -> FeatureJoiner_10 [LEFT]
Note: Weekends passed
FeatureJoiner_9
    ATTR_CONFLICT_RES_LOOKUP = USE_LEFT
    GEOMETRY_HANDLING_LOOKUP = USE_LEFT
    JOIN_KEYS = stop_id stop_id AUTO
    JOIN_MODE = Inner
    ATTR_CONFLICT_RES = Prefer Left
    GEOMETRY_HANDLING = Prefer Left
    JOINED -> FeatureJoiner_10 [RIGHT]
Note: Weekdays And Weekends passed
FeatureJoiner_10
    ATTR_CONFLICT_RES_LOOKUP = USE_LEFT
    GEOMETRY_HANDLING_LOOKUP = USE_LEFT
    JOIN_KEYS = stop_id stop_id AUTO
    JOIN_MODE = Inner
    ATTR_CONFLICT_RES = Prefer Left
    GEOMETRY_HANDLING = Prefer Left
    JOINED -> FeatureJoiner_11 [LEFT]
Note: Getting Original Attributes
FeatureJoiner_11
    ATTR_CONFLICT_RES_LOOKUP = USE_RIGHT
    GEOMETRY_HANDLING_LOOKUP = USE_RIGHT
    JOIN_KEYS = stop_id stop_id AUTO
    JOIN_MODE = Inner
    ATTR_CONFLICT_RES = Prefer Right
    GEOMETRY_HANDLING = Prefer Right
    JOINED -> AttributeManager_2
Note: Add Frequency_type
AttributeManager_2
    ATTR_TABLE:
      SET_TO Frequency_type (varchar(30)) = Has at least $(MinServicePerHour) stop(s) per hour
      REMOVE hour.total_count (uint64)
      REMOVE departure_time (uint32)
      REMOVE arrival_time (uint32)
      REMOVE service_id (varchar(13))
      REMOVE start_date (uint32)
      REMOVE end_date (uint32)
      REMOVE hh_text (varchar(200))
      REMOVE route_type (uint16)
    USER_EXPOSED_ATTRIBUTES = Frequency_type
    -> Sorter
Note: Only for review purposes
Sorter
    SORT_PARM = stop_id NATURAL ASCENDING NON_VALUES_AFTER_VALUES monday NATURAL DESCENDING NON_VALUES_AFTER_VALUES tuesday NATURAL DESCENDING NON_VALUES_AFTER_VALUES wednesday NATURAL DESCENDING NON_VALUES_AFTER_VALUES thursday NATURAL DESCENDING NON_VALUES_AFTER_VALUES friday NATURAL DESCENDING NON_VALUES_AFTER_VALUES saturday NATURAL DESCENDING NON_VALUES_AFTER_VALUES sunday NATURAL DESCENDING NON_VALUES_AFTER_VALUES hour NATURAL ASCENDING NON_VALUES_AFTER_VALUES
    SORTED -> TestFilter

Bookmark: Wednesday
Note: Service on Wednesdays 6-21
Tester_11
    BOOL_OP = COMPOSITE
    COMPOSITE_TEST = 1 AND 2 AND 3
    TEST_CLAUSE:
      TEST @Value(wednesday) = 1
      TEST @Value(hour) >= 6
      TEST @Value(hour) < 21
    TEST_MODE = TEST
    PASSED -> StatisticsCalculator_3
Note: Total count of services per stop_id, hour
StatisticsCalculator_3
    ATTR_ACCUM_MODE = None
    CALCULATION_MODE = NUMERIC
    FEAT_STATS = hour,NUMERIC_MODE,,,COUNT,,,,,,,,,,
    GROUP_BY = stop_id hour
    SUMMARY -> AttributeManager_5
Note: Rename attribute
AttributeManager_5
    ATTR_TABLE = RENAME_SET_VALUE hour.total_count > service per hour (uint64)
    -> Tester_12
Note: If there are >=N services in every hour
Tester_12
    BOOL_OP = OR
    TEST_CLAUSE = TEST @Value(service per hour) >= $(MinServicePerHour)
    TEST_MODE = TEST
    PASSED -> StatisticsCalculator_10
Note: Count of hours with ≥N services per stop
StatisticsCalculator_10
    ATTR_ACCUM_MODE = None
    CALCULATION_MODE = NUMERIC
    FEAT_STATS = hour,NUMERIC_MODE,,,COUNT,,,,,,,,,,
    GROUP_BY = stop_id
    SUMMARY -> Tester_23
Note: Stops with >=N services in 6-21
Tester_23
    BOOL_OP = OR
    TEST_CLAUSE = TEST @Value(hour.total_count) = 15
    TEST_MODE = TEST
    PASSED -> FeatureJoiner_6 [RIGHT]

Bookmark: Thursday
Note: Service on Thursdays 6-21
Tester_13
    BOOL_OP = COMPOSITE
    COMPOSITE_TEST = 1 AND 2 AND 3
    TEST_CLAUSE:
      TEST @Value(thursday) = 1
      TEST @Value(hour) >= 6
      TEST @Value(hour) < 21
    TEST_MODE = TEST
    PASSED -> StatisticsCalculator_4
Note: Total count of services per stop_id, hour
StatisticsCalculator_4
    ATTR_ACCUM_MODE = None
    CALCULATION_MODE = NUMERIC
    FEAT_STATS = hour,NUMERIC_MODE,,,COUNT,,,,,,,,,,
    GROUP_BY = stop_id hour
    SUMMARY -> AttributeManager_6
Note: Rename attribute
AttributeManager_6
    ATTR_TABLE = RENAME_SET_VALUE hour.total_count > service per hour (uint64)
    -> Tester_14
Note: If there are >=N services in every hour
Tester_14
    BOOL_OP = OR
    TEST_CLAUSE = TEST @Value(service per hour) >= $(MinServicePerHour)
    TEST_MODE = TEST
    PASSED -> StatisticsCalculator_11
Note: Count of hours with ≥N services per stop
StatisticsCalculator_11
    ATTR_ACCUM_MODE = None
    CALCULATION_MODE = NUMERIC
    FEAT_STATS = hour,NUMERIC_MODE,,,COUNT,,,,,,,,,,
    GROUP_BY = stop_id
    SUMMARY -> Tester_24
Note: Stops with >=N services in 6-21
Tester_24
    BOOL_OP = OR
    TEST_CLAUSE = TEST @Value(hour.total_count) = 15
    TEST_MODE = TEST
    PASSED -> FeatureJoiner_7 [RIGHT]

Bookmark: Friday
Note: Service on Fridays 6-21
Tester_15
    BOOL_OP = COMPOSITE
    COMPOSITE_TEST = 1 AND 2 AND 3
    TEST_CLAUSE:
      TEST @Value(friday) = 1
      TEST @Value(hour) >= 6
      TEST @Value(hour) < 21
    TEST_MODE = TEST
    PASSED -> StatisticsCalculator_5
Note: Total count of services per stop_id, hour
StatisticsCalculator_5
    ATTR_ACCUM_MODE = None
    CALCULATION_MODE = NUMERIC
    FEAT_STATS = hour,NUMERIC_MODE,,,COUNT,,,,,,,,,,
    GROUP_BY = stop_id hour
    SUMMARY -> AttributeManager_7
Note: Rename attribute
AttributeManager_7
    ATTR_TABLE = RENAME_SET_VALUE hour.total_count > service per hour (uint64)
    -> Tester_16
Note: If there are >=N services in every hour
Tester_16
    BOOL_OP = OR
    TEST_CLAUSE = TEST @Value(service per hour) >= $(MinServicePerHour)
    TEST_MODE = TEST
    PASSED -> StatisticsCalculator_12
Note: Count of hours with ≥N services per stop
StatisticsCalculator_12
    ATTR_ACCUM_MODE = None
    CALCULATION_MODE = NUMERIC
    FEAT_STATS = hour,NUMERIC_MODE,,,COUNT,,,,,,,,,,
    GROUP_BY = stop_id
    SUMMARY -> Tester_25
Note: Stops with >=N services in 6-21
Tester_25
    BOOL_OP = OR
    TEST_CLAUSE = TEST @Value(hour.total_count) = 15
    TEST_MODE = TEST
    PASSED -> FeatureJoiner_8 [RIGHT]

Bookmark: Saturday
Note: Service on Saturdays 8-18
Tester_17
    BOOL_OP = COMPOSITE
    COMPOSITE_TEST = 1 AND 2 AND 3
    TEST_CLAUSE:
      TEST @Value(saturday) = 1
      TEST @Value(hour) >= 8
      TEST @Value(hour) < 18
    TEST_MODE = TEST
    PASSED -> StatisticsCalculator_6
Note: Total count of services per stop_id, hour
StatisticsCalculator_6
    ATTR_ACCUM_MODE = None
    CALCULATION_MODE = NUMERIC
    FEAT_STATS = hour,NUMERIC_MODE,,,COUNT,,,,,,,,,,
    GROUP_BY = stop_id hour
    SUMMARY -> AttributeManager_8
Note: Rename attribute
AttributeManager_8
    ATTR_TABLE = RENAME_SET_VALUE hour.total_count > service per hour (uint64)
    -> Tester_18
Note: If there are >=N services in every hour
Tester_18
    BOOL_OP = OR
    TEST_CLAUSE = TEST @Value(service per hour) >= $(MinServicePerHour)
    TEST_MODE = TEST
    PASSED -> StatisticsCalculator_13
Note: Count of hours with ≥N services per stop
StatisticsCalculator_13
    ATTR_ACCUM_MODE = None
    CALCULATION_MODE = NUMERIC
    FEAT_STATS = hour,NUMERIC_MODE,,,COUNT,,,,,,,,,,
    GROUP_BY = stop_id
    SUMMARY -> Tester_26
Note: Stops with >=N services in 6-21
Tester_26
    BOOL_OP = OR
    TEST_CLAUSE = TEST @Value(hour.total_count) = 10
    TEST_MODE = TEST
    PASSED -> FeatureJoiner_9 [LEFT]

Bookmark: Sunday
Note: Service on Sundays 8-18
Tester_19
    BOOL_OP = COMPOSITE
    COMPOSITE_TEST = 1 AND 2 AND 3
    TEST_CLAUSE:
      TEST @Value(sunday) = 1
      TEST @Value(hour) >= 8
      TEST @Value(hour) < 18
    TEST_MODE = TEST
    PASSED -> StatisticsCalculator_7
Note: Total count of services per stop_id, hour
StatisticsCalculator_7
    ATTR_ACCUM_MODE = None
    CALCULATION_MODE = NUMERIC
    FEAT_STATS = hour,NUMERIC_MODE,,,COUNT,,,,,,,,,,
    GROUP_BY = stop_id hour
    SUMMARY -> AttributeManager_9
Note: Rename attribute
AttributeManager_9
    ATTR_TABLE = RENAME_SET_VALUE hour.total_count > service per hour (uint64)
    -> Tester_20
Note: If there are >=N services in every hour
Tester_20
    BOOL_OP = OR
    TEST_CLAUSE = TEST @Value(service per hour) >= $(MinServicePerHour)
    TEST_MODE = TEST
    PASSED -> StatisticsCalculator_14
Note: Count of hours with ≥N services per stop
StatisticsCalculator_14
    ATTR_ACCUM_MODE = None
    CALCULATION_MODE = NUMERIC
    FEAT_STATS = hour,NUMERIC_MODE,,,COUNT,,,,,,,,,,
    GROUP_BY = stop_id
    SUMMARY -> Tester_27
Note: Stops with >=N services in 6-21
Tester_27
    BOOL_OP = OR
    TEST_CLAUSE = TEST @Value(hour.total_count) = 10
    TEST_MODE = TEST
    PASSED -> FeatureJoiner_9 [RIGHT]

Bookmark: Write Outputs
Note: Specify The Format To Write
TestFilter
    DEFAULT_VALUE = <UNFILTERED>
    PASSED_TEST_GROUP_OUTPUT = FIRST
    TEST_LIST = "BOOL_OP,OR,COMPOSITE_TEST,""""""1"""""",TEST_CLAUSE,TEST $(outFormat) = gpkg",gpkg,"BOOL_OP,OR,COMPOSITE_TEST,""""""1"""""",TEST_CLAUSE,TEST $(outFormat) = shp",shp,"BOOL_OP,OR,COMPOSITE_TEST,""""""1"""""",TEST_CLAUSE,TEST $(outFormat) = xslx",xlsx
    gpkg -> FeatureWriter [Table1]
    shp -> FeatureWriter_2 [Sheet1]
    xlsx -> FeatureWriter_3 [Output]
Note: Geopackage Format
FeatureWriter
    DATASET = $(outFolder)\$(outName).gpkg
    DATASET_ATTR = _dataset
    FEATURE_TYPE_LIST_ATTR = _feature_types
    FORMAT = OGCGEOPACKAGE
    OGCGEOPACKAGE_ALWAYS_CREATE_FEATURE_TYPES = NO
    OGCGEOPACKAGE_CASE_CONTROL_ATTR_NAMES = lower
    OGCGEOPACKAGE_CASE_CONTROL_FT_NAMES = none
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_VERSION = 1.2
    OGCGEOPACKAGE_WRITE_NULLS = YES
    TOTAL_FEATURES_WRITTEN_ATTR = _total_features_written
Note: ShapeFile format
FeatureWriter_2
    DATASET = $(outFolder)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Note: Excel Format
FeatureWriter_3
    DATASET = $(outFolder)\$(outName).xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- ZIP_PATH =   # Source Zip File
- ROOT_FOLDER =   # Destination Root Folder
- REPLACE = No   # Replace Existing Destination Subfolder
- RECURSIVE = No   # Unzip Nested Zip Files Recursively
- PRESERVE = No   # Preserve Nested Zip Files
- EXT_S =   # Allowable Source Zip File Extension(s)
- EXT_N =   # Allowable Nested Zip File Extension(s)

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.zip_path __unzipper.ext_s __unzipper.replace __unzipper.recursive __unzipper.root_folder __unzipper.preserve
    NEW_ATTRIBUTES = path_unix path_windows path_depth __unzipper.flag _error_message
    PYTHONSOURCE:
      # 2016-01-21, Takashi Iijima, Original Implementation
      # 2016-01-23, Takashi Iijima, Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-25, Takashi Iijima, Updated to trim leading and trailing whitespaces of specified path strings.
      # 2018-06-14, Takashi Iijima, Added Allowable Source/Nested Zip File Extention(s) parameter.
      # 2019-01-13, Takashi Iijima, Fixed the destination folder name derived from zip filename which has non-4-letters suffix (e.g. ".xlsx").
      # 2020-01-13, Takashi Iijima, Changed Default Python Interpreter to 3.6+, saved with FME 2017.1.2.1

      import fmeobjects, zipfile, os

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip']) # Filename extensions source (root) zip files
              self.zipExtN = set(['.zip']) # Filename extensions for archived (descendant) zip files

          # Returns the number of characters of the zip file extension
          # if the path points a valid zip file, 0 otherwise.
          def zipExtLen(self, path, zipExt):
              _, ext = os.path.splitext(path)
              return len(ext) if (ext.lower() in zipExt and zipfile.is_zipfile(path)) else 0

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) \
                  or self.zipExtLen(zipPath, self.zipExtS) == 0 \
                  or not isRootValid:
                  msg = 'Specified zip file or destination root folder is invalid.'
                  self.logger.logMessageString(msg, fmeobjects.FME_ERROR)
                  feature.setAttribute('_error_message', msg)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              rootName, _ = os.path.splitext(zipName)
              destFolder = os.path.join(os.path.abspath(rootFolder) if rootFolder else zipFolder, rootName)

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath, destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  msg = 'Unexpected error: %s' % ex
                  self.logger.logMessageString(msg, fmeobjects.FME_ERROR)
                  feature.setAttribute('_error_message', msg)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive:
                      n = self.zipExtLen(path, self.zipExtN)
                      if n != 0:
                          if self.preserve:
                              self.pathInfos.append((path, self.kFlagFile, depth))
                              self.extract(path, os.path.join(dirPath, fname[:-n]), depth)
                          else:
                              self.extract(path, os.path.join(dirPath, fname[:-n]), depth)
                              os.remove(path)
                      else:
                          self.pathInfos.append((path, self.kFlagFile, depth))
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> <Rejected> (output)
File (output)
Directory (output)
<Rejected> (output)
